# SPDX-License-Identifier: LGPL-2.1-or-later

import math
import os
from PySide import QtCore, QtGui
from dataclasses import dataclass

import FreeCAD as App
import FreeCADGui as Gui
import Part
import Sketcher


@dataclass
class RibParameters:
    # Thread General
    name: str
    normative: float
    core_diameter: float
    core_bore: float

    # Rib Specific
    entrance_depth: float
    outer_diameter: float
    rib_engagement: float
    rib_diameter: float
    verified: bool


# fmt: off
RIB_PARAMETERS = {
    "M3": RibParameters(name="M3", normative=3, core_diameter=2.39, core_bore=2.5, entrance_depth=0.6, outer_diameter=3.4, rib_engagement=0.2, rib_diameter=1.4, verified=True),
    "M4": RibParameters(name="M4", normative=4, core_diameter=3.14, core_bore=3.3, entrance_depth=0.8, outer_diameter=4.4, rib_engagement=0.3, rib_diameter=1.6, verified=True),
    "M5": RibParameters(name="M5", normative=5, core_diameter=4.02, core_bore=4.2, entrance_depth=1.0, outer_diameter=5.4, rib_engagement=0.4, rib_diameter=2.0, verified=True),
    "M6": RibParameters(name="M6", normative=6, core_diameter=4.77, core_bore=5.0, entrance_depth=1.2, outer_diameter=6.4, rib_engagement=0.5, rib_diameter=2.2, verified=True),
    "M8": RibParameters(name="M8", normative=8, core_diameter=6.47, core_bore=6.8, entrance_depth=1.4, outer_diameter=8.5, rib_engagement=0.5, rib_diameter=2.6, verified=True),
}
# fmt: on

# Aliases for newer FreeCAD versions
RIB_PARAMETERS["M3x0.5"] = RIB_PARAMETERS["M3"]
RIB_PARAMETERS["M4x0.7"] = RIB_PARAMETERS["M4"]
RIB_PARAMETERS["M5x0.8"] = RIB_PARAMETERS["M5"]
RIB_PARAMETERS["M6x1.0"] = RIB_PARAMETERS["M6"]
RIB_PARAMETERS["M6x1"] = RIB_PARAMETERS["M6"]
RIB_PARAMETERS["M8x1.25"] = RIB_PARAMETERS["M8"]


def abort_with_error(msg):
    filename = os.path.basename(__file__)
    diag = QtGui.QMessageBox(QtGui.QMessageBox.Warning, f"Error in {filename}", msg)
    diag.setWindowModality(QtCore.Qt.ApplicationModal)
    diag.exec_()
    raise Exception(msg)


def confirm_proceed(msg):
    filename = os.path.basename(__file__)
    print(f"Warning: {msg}")
    reply = QtGui.QMessageBox.question(None, f"Error in {filename}", f"{msg}\nProceed anyway?")
    if reply != QtGui.QMessageBox.Yes:
        raise Exception(msg)
    print("Proceeding anyway...")


def make_derived_sketch(body, original, suffix):
    sketch = body.newObject("Sketcher::SketchObject", original.Name + suffix)
    sketch.AttachmentSupport = [(original, "")]
    sketch.MapMode = "ObjectXY"
    sketch.Label = original.Label + suffix
    sketch.recompute()
    return sketch


def make_parametric_circle(sketch, center_expr, size_expr):
    last_geo_id = len(sketch.Geometry)
    new_geo = [
        Part.Circle(App.Vector(0, 0, 0), App.Vector(0, 0, 1), 2),
    ]
    sketch.addGeometry(new_geo, False)
    last_c = len(sketch.Constraints)
    new_constraints = [
        Sketcher.Constraint("DistanceX", last_geo_id + 0, 3, 0),
        Sketcher.Constraint("DistanceY", last_geo_id + 0, 3, 0),
        Sketcher.Constraint("Diameter", last_geo_id + 0, 2),
    ]
    sketch.addConstraint(new_constraints)
    sketch.setExpression(f"Constraints[{last_c + 0}]", f"{center_expr}.x * 1mm")
    sketch.setExpression(f"Constraints[{last_c + 1}]", f"{center_expr}.y * 1mm")
    sketch.setExpression(f"Constraints[{last_c + 2}]", f"{size_expr}")
    sketch.recompute()


def get_or_create_rib_template(doc, rib_param: RibParameters):
    name = f"Sketch_{rib_param.name}_RibThreadTemplate"
    sketch = doc.getObject(name)
    if sketch is not None:
        return sketch

    sketch = doc.addObject("Sketcher::SketchObject", name)

    center_circle = Part.Circle(App.Vector(0, 0, 0), App.Vector(0, 0, 1), rib_param.outer_diameter / 2)
    rib_center_radius = (rib_param.normative - rib_param.rib_engagement * 2 + rib_param.rib_diameter) / 2
    rib_center_circle = Part.Circle(App.Vector(0, 0, 0), App.Vector(0, 0, 1), rib_center_radius)

    rib_center_circle_id = len(sketch.Geometry)
    sketch.addGeometry(rib_center_circle)
    sketch.toggleConstruction(rib_center_circle_id)

    normative_circle_id = len(sketch.Geometry)
    sketch.addGeometry(Part.Circle(App.Vector(0, 0, 0), App.Vector(0, 0, 1), rib_param.normative / 2))
    sketch.toggleConstruction(normative_circle_id)

    core_circle_id = len(sketch.Geometry)
    sketch.addGeometry(Part.Circle(App.Vector(0, 0, 0), App.Vector(0, 0, 1), rib_param.core_diameter / 2))
    sketch.toggleConstruction(core_circle_id)

    rib_arc_ids = len(sketch.Geometry)
    center_angles = []
    for i in range(3):
        a = i * math.pi * 2 / 3
        rib_center = App.Vector(math.cos(a) * rib_center_radius, math.sin(a) * rib_center_radius, 0)
        rib_circle = Part.Circle(
            rib_center,
            App.Vector(0, 0, 1),
            rib_param.rib_diameter / 2,
        )
        intersections = center_circle.intersect(rib_circle)
        if len(intersections) != 2:
            abort_with_error("ribs do not intersect outer diameter, cannot proceed!")

        center_angles += [math.atan2(p.Y, p.X) for p in intersections]

        rib_intersections = [App.Vector(p.X, p.Y, 0) - rib_center for p in intersections]
        rib_angles = [math.atan2(p.y, p.x) for p in rib_intersections]

        sketch.addGeometry(Part.ArcOfCircle(rib_circle, rib_angles[0], rib_angles[1]))

    assert len(center_angles) == 6
    center_angles.sort()

    center_arc_ids = len(sketch.Geometry)
    new_geo = [
        Part.ArcOfCircle(center_circle, center_angles[1], center_angles[2]),
        Part.ArcOfCircle(center_circle, center_angles[3], center_angles[4]),
        Part.ArcOfCircle(center_circle, center_angles[5], center_angles[0]),
    ]
    sketch.addGeometry(new_geo, False)

    new_constraints = [
        # Arc End Coincidences
        Sketcher.Constraint("Coincident", center_arc_ids + 0, 2, rib_arc_ids + 0, 2),
        Sketcher.Constraint("Coincident", center_arc_ids + 1, 1, rib_arc_ids + 0, 1),
        Sketcher.Constraint("Coincident", center_arc_ids + 1, 2, rib_arc_ids + 1, 2),
        Sketcher.Constraint("Coincident", center_arc_ids + 2, 1, rib_arc_ids + 1, 1),
        Sketcher.Constraint("Coincident", center_arc_ids + 2, 2, rib_arc_ids + 2, 2),
        Sketcher.Constraint("Coincident", center_arc_ids + 0, 1, rib_arc_ids + 2, 1),
        # Arc Centers
        Sketcher.Constraint("Coincident", rib_center_circle_id, 3, -1, 1),
        Sketcher.Constraint("Coincident", normative_circle_id, 3, -1, 1),
        Sketcher.Constraint("Coincident", core_circle_id, 3, -1, 1),
        Sketcher.Constraint("Coincident", center_arc_ids + 0, 3, -1, 1),
        Sketcher.Constraint("Coincident", center_arc_ids + 1, 3, -1, 1),
        Sketcher.Constraint("Coincident", center_arc_ids + 2, 3, -1, 1),
        Sketcher.Constraint("PointOnObject", rib_arc_ids + 0, 3, rib_center_circle_id),
        Sketcher.Constraint("PointOnObject", rib_arc_ids + 1, 3, rib_center_circle_id),
        Sketcher.Constraint("PointOnObject", rib_arc_ids + 2, 3, rib_center_circle_id),
        # Arc Equalities
        Sketcher.Constraint("Equal", center_arc_ids + 0, center_arc_ids + 1),
        Sketcher.Constraint("Equal", center_arc_ids + 0, center_arc_ids + 2),
        Sketcher.Constraint("Equal", rib_arc_ids + 0, rib_arc_ids + 1),
        Sketcher.Constraint("Equal", rib_arc_ids + 0, rib_arc_ids + 2),
    ]
    sketch.addConstraint(new_constraints)

    dia_constraint_ids = len(sketch.Constraints)
    new_constraints = [
        # Diameters
        Sketcher.Constraint("Diameter", rib_center_circle_id, rib_center_radius * 2),
        Sketcher.Constraint("Diameter", center_arc_ids + 0, rib_param.outer_diameter),
        Sketcher.Constraint("Diameter", rib_arc_ids + 0, rib_param.rib_diameter),
        Sketcher.Constraint("Diameter", normative_circle_id, rib_param.normative),
        Sketcher.Constraint("Diameter", core_circle_id, rib_param.core_diameter),
    ]
    sketch.addConstraint(new_constraints)
    sketch.renameConstraint(dia_constraint_ids + 1, "outer_diameter")
    sketch.renameConstraint(dia_constraint_ids + 2, "rib_diameter")
    sketch.renameConstraint(dia_constraint_ids + 3, "normative_diameter")
    sketch.renameConstraint(dia_constraint_ids + 4, "core_diameter")

    # Lines for distance between ribs
    line_ids = len(sketch.Geometry)
    for i in range(3):
        center1 = sketch.Geometry[rib_arc_ids + i].Center
        center2 = sketch.Geometry[rib_arc_ids + ((i + 1) % 3)].Center

        line_id = len(sketch.Geometry)
        sketch.addGeometry(Part.LineSegment(center1, center2))
        sketch.toggleConstruction(line_id)
        new_constraints = [
            Sketcher.Constraint("Coincident", line_id, 1, rib_arc_ids + i, 3),
            Sketcher.Constraint("Coincident", line_id, 2, rib_arc_ids + ((i + 1) % 3), 3),
        ]
        sketch.addConstraint(new_constraints)

    # Constrain distance between ribs to be equal
    new_constraints = [
        Sketcher.Constraint("Equal", line_ids + 0, line_ids + 1),
        Sketcher.Constraint("Equal", line_ids + 0, line_ids + 2),
    ]
    sketch.addConstraint(new_constraints)

    # Finally, constrain rotation of the ribs around the center
    new_constraints = [
        Sketcher.Constraint("PointOnObject", rib_arc_ids + 0, 3, -1),
    ]
    sketch.addConstraint(new_constraints)

    sketch.Visibility = False
    sketch.recompute()

    return sketch


def make_sketch_offset_shape_binder(*, body, template, sketch, index, center_expr, rotation_expr):
    shape_binder = body.newObject("PartDesign::SubShapeBinder", f"{sketch.Name}_RibThread{index + 1:03}")
    shape_binder.Support = (template, "")
    shape_binder.Relative = False
    shape_binder.Visibility = False
    shape_binder.setExpression(
        "Placement",
        f"{sketch.Name}.Placement * placement({center_expr}; rotation({rotation_expr}; 0; 0))",
    )
    return shape_binder


def make_rib_thread(body, hole):
    if not hole.Threaded:
        confirm_proceed("selected Hole is not threaded. will most likely generate broken rib-threads!")

    if hole.ModelThread:
        abort_with_error("cannot generated rib-threads on a Hole with modelled threads!")

    if hole.Tapered:
        abort_with_error("cannot generated rib-threads on a tapered Hole!")

    if hole.ThreadSize not in RIB_PARAMETERS:
        abort_with_error(f'thread size "{hole.ThreadSize}" is not yet known, please add parameters!')

    rib_param = RIB_PARAMETERS[hole.ThreadSize]

    if not rib_param.verified:
        confirm_proceed(
            "the rib-thread parameters for this thread size have not yet been verified.\n"
            + "they will probably work, but please test this before relying on them...\n"
            + "if you are really nice, after testing, let me know about your results!"
        )

    if hole.Diameter > (rib_param.normative - rib_param.rib_engagement * 2):
        confirm_proceed("drill diameter of Hole is too big for ribs - they will get cut off!")

    if len(hole.Profile) < 1:
        abort_with_error("missing hole profile")

    profile_sketch = hole.Profile[0]
    if profile_sketch.TypeId != "Sketcher::SketchObject":
        abort_with_error("hole profile is not a Sketch object")

    # Only generate the varset if it does not exist yet
    varset = body.getObject(f"{hole.Name}_RibThread_Settings")
    if varset is None:
        varset = body.newObject("App::VarSet", f"{hole.Name}_RibThread_Settings")
        varset.Label = f"{hole.Label}_RibThread"
        varset.addProperty("App::PropertyLength", "EntranceDepth", "Base")
        varset.addProperty("App::PropertyLength", "EntranceDiameter", "Base")
        varset.addProperty("App::PropertyAngle", "Rotation", "Base")
        varset.EntranceDepth = f"{rib_param.entrance_depth} mm"
        varset.EntranceDiameter = f"{rib_param.outer_diameter} mm"
        varset.Rotation = "0 deg"
        varset.recompute()

    rib_template = get_or_create_rib_template(App.ActiveDocument, rib_param)
    sketch_entrance = make_derived_sketch(body, profile_sketch, "_ThreadEntrance")

    shape_binders = []
    for index, circle in enumerate(profile_sketch.Geometry):
        if circle.TypeId != "Part::GeomCircle":
            continue

        make_parametric_circle(
            sketch_entrance,
            f"{profile_sketch.Name}.Geometry[{index}].Center",
            f"{varset.Name}.EntranceDiameter",
        )

        binder = make_sketch_offset_shape_binder(
            body=body,
            template=rib_template,
            sketch=profile_sketch,
            index=index,
            center_expr=f"{profile_sketch.Name}.Geometry[{index}].Center",
            rotation_expr=f"{varset.Name}.Rotation",
        )
        shape_binders.append(binder)

    # Create merged shape-binder
    merged_binder = body.newObject("PartDesign::SubShapeBinder", f"{hole.Name}_RibThreads")
    merged_binder.Support = [(b, "") for b in shape_binders]
    merged_binder.Relative = True
    merged_binder.ViewObject.LineColor = (1.0, 0.84, 0.0, 0.60)
    merged_binder.ViewObject.PointColor = (1.0, 0.84, 0.0, 0.60)
    m = merged_binder.ViewObject.ShapeAppearance[0]
    m.DiffuseColor = (1.0, 0.84, 0.0, 0.60)
    merged_binder.ViewObject.ShapeAppearance = (m,)
    merged_binder.ViewObject.Transparency = 60
    merged_binder.recompute()

    pocket_ribs = body.newObject("PartDesign::Pocket", f"{hole.Name}_ThreadRibs")
    pocket_ribs.Profile = (merged_binder, "")
    pocket_ribs.Reversed = hole.Reversed
    merged_binder.Visibility = False
    pocket_ribs.setExpression("Type", f"{hole.Name}.DepthType")
    pocket_ribs.setExpression("Length", f"{hole.Name}.Depth")
    pocket_ribs.Label = f"{hole.Label}_ThreadRibs"
    pocket_ribs.recompute()

    if hole.Reversed:
        sketch_entrance.setExpression(".AttachmentOffset.Base.z", f"{varset.Name}.EntranceDepth")
    else:
        sketch_entrance.setExpression(".AttachmentOffset.Base.z", f"-{varset.Name}.EntranceDepth")
    sketch_entrance.recompute()

    pocket_entrance = body.newObject("PartDesign::Pocket", f"{hole.Name}_ThreadEntrance")
    pocket_entrance.Profile = (sketch_entrance, "")
    pocket_entrance.ReferenceAxis = (sketch_entrance, ["N_Axis"])
    pocket_entrance.Reversed = hole.Reversed
    pocket_entrance.Type = "TwoLengths"
    pocket_entrance.TaperAngle = "-20 deg"
    sketch_entrance.Visibility = False
    # 2.8 is roughly the tan(90 - 20 deg), so the taper will be complete
    pocket_entrance.setExpression("Length", f"({varset.Name}.EntranceDiameter - {hole.Name}.Diameter) * 2.8")
    pocket_entrance.setExpression("Length2", f"{varset.Name}.EntranceDepth")
    pocket_entrance.Label = f"{hole.Label}_ThreadEntrance"
    pocket_entrance.recompute()


active_body = Gui.ActiveDocument.ActiveView.getActiveObject("pdbody")

sel = Gui.Selection.getSelection()
if len(sel) == 0:
    abort_with_error("no Hole object selected")
if len(sel) > 1:
    abort_with_error("more than one object selected")

hole_obj = Gui.Selection.getSelection()[0]
if hole_obj.getParent() != active_body:
    abort_with_error("selected object is not part of the active body")
if hole_obj.TypeId != "PartDesign::Hole":
    abort_with_error("selected object is not a PartDesign Hole feature")

try:
    # Open a transaction so the operation can be easily undone
    App.ActiveDocument.openTransaction("Add upside down counterbores")
    make_rib_thread(active_body, hole_obj)
    App.ActiveDocument.commitTransaction()
except Exception as e:
    # When an error occurred, abort the entire transaction and rollback
    App.ActiveDocument.abortTransaction()
    raise e from None
